-- eCall MSD ASN.1 Schema (EN 15722:2019)
-- Minimum Set of Data for eCall
-- Based on actual eCall MSD standard structure

ECallMSD DEFINITIONS AUTOMATIC TAGS ::= BEGIN

-- Top-level MSD Message
CurrentVersion::=INTEGER(2)

ECallMessage ::= SEQUENCE{
    msdVersion      INTEGER(0..255),
    msd OCTET STRING (CONTAINING MSDMessage)
}


MSDMessage ::= SEQUENCE {
    msdStructure MSDStructure,
    optionalData OCTET STRING (SIZE(1..1400)) OPTIONAL
}

-- Core MSD Structure
MSDStructure ::= SEQUENCE {
    messageIdentifier INTEGER (0..255),
    control ControlType,
    vehicleIdentificationNumber VIN,
    vehiclePropulsionStorageType VehiclePropulsionStorageType,
    timestamp INTEGER (0..4294967295),
    vehicleLocation VehicleLocation,
    vehicleDirection INTEGER (0..255),
    recentVehicleLocationN1 VehicleLocationDelta OPTIONAL,
    recentVehicleLocationN2 VehicleLocationDelta OPTIONAL,
    numberOfPassengers INTEGER (0..255) OPTIONAL,
    additionalData OCTET STRING (SIZE(1..255)) OPTIONAL
}

-- Control Bits
ControlType ::= SEQUENCE {
    automaticActivation     BOOLEAN,
    testCall                BOOLEAN,
    positionCanBeTrusted    BOOLEAN,
    vehicleType             VehicleType
} 

-- Vehicle Identification Number (17 characters per ISO 3779)

VehiclePropulsionStorageType ::= SEQUENCE{
    gasolineTankPresent         BOOLEAN DEFAULT FALSE,
    dieselTankPresent           BOOLEAN DEFAULT FALSE,
    compressedNaturalGas        BOOLEAN DEFAULT FALSE,
    liquidPropaneGas            BOOLEAN DEFAULT FALSE,
    hydrogenStorage             BOOLEAN DEFAULT FALSE,
    otherStorage                BOOLEAN DEFAULT FALSE,
    ...
}

VIN ::= SEQUENCE {
    isowmin PrintableString (SIZE(3)),
    isovds PrintableString (SIZE(6)),
    isovisModelyear PrintableString (SIZE(1)),
    isovisSeqPlant PrintableString (SIZE(7))
}

-- Vehicle Type and Propulsion/Storage
VehicleType ::= ENUMERATED {
    passengerVehicleClassM1 (1),
    passengerVehicleClassM2 (2),
    passengerVehicleClassM3 (3),
    lightCommercialVehicleClassM1   (4),
    heavyDutyVehicleClassN2 (5),
    heavyDutyVehicleClassN3 (6),
    motorcycleClassL1e  (7),
    motorcycleClassL2e  (8),
    motorcycleClassL3e  (9)
} 

-- Vehicle Location (Latitude and Longitude deltas in 1/10 second precision)
VehicleLocation ::= SEQUENCE {
    positionLatitude        INTEGER (-2147483648..2147483647),
    positionLongitude       INTEGER (-2147483648..2147483647),
    ...
}

VehicleLocationDelta ::= SEQUENCE {
    latitudeDelta       INTEGER (-512..511),
    longitudeDelta      INTEGER (-512..511)
}

AdditionalData ::= SEQUENCE {
    oid         OBJECT IDENTIFIER,
    data        OCTET STRING
}

END
